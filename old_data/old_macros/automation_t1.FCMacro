# -*- coding: utf-8 -*-

# Macro Begin: C:\Users\aadit\atelier_windows\freecad_models\macros\automation_t1.FCMacro +++++++++++++++++++++++++++++++++++++++++++++++++
import FreeCAD
import PartDesign
import PartDesignGui
import Sketcher

# Gui.runCommand('Std_DlgMacroRecord',0)
### Begin command Std_Workbench
# Gui.activateWorkbench("PartDesignWorkbench")
### End command Std_Workbench
### Begin command PartDesign_Body
App.activeDocument().addObject('PartDesign::Body','Body')
App.ActiveDocument.getObject('Body').Label = 'Body'
# import PartDesignGui
# Gui.activateView('Gui::View3DInventor', True)
# Gui.activeView().setActiveObject('pdbody', App.activeDocument().Body)
# Gui.Selection.clearSelection()
# Gui.Selection.addSelection(App.ActiveDocument.Body)
App.ActiveDocument.recompute()
### End command PartDesign_Body
# Gui.Selection.addSelection('Unnamed','Body')
# Gui.runCommand('PartDesign_NewSketch',0)
# Gui.Selection.clearSelection()
# Gui.Selection.addSelection('Unnamed','Body','Origin.XY_Plane.')
App.getDocument('Unnamed').getObject('Body').newObject('Sketcher::SketchObject','Sketch')
App.getDocument('Unnamed').getObject('Sketch').Support = (App.getDocument('Unnamed').getObject('XY_Plane'),[''])
App.getDocument('Unnamed').getObject('Sketch').MapMode = 'FlatFace'
App.ActiveDocument.recompute()
# Gui.getDocument('Unnamed').setEdit(App.getDocument('Unnamed').getObject('Body'), 0, 'Sketch.')
# ActiveSketch = App.getDocument('Unnamed').getObject('Sketch')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Unnamed').getObject('Body'), 'Sketch.'))
# if ActiveSketch.ViewObject.ShowSupport:
#   tv.show([ref[0] for ref in ActiveSketch.Support if not ref[0].isDerivedFrom("PartDesign::Plane")])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Unnamed').getObject('Sketch')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.Selection.clearSelection()
# Gui.runCommand('Sketcher_CompCreateRectangles',0)
geoList = []
geoList.append(Part.LineSegment(App.Vector(-34.213100,23.998047,0),App.Vector(33.822094,23.998047,0)))
geoList.append(Part.LineSegment(App.Vector(33.822094,23.998047,0),App.Vector(33.822094,-20.087975,0)))
geoList.append(Part.LineSegment(App.Vector(33.822094,-20.087975,0),App.Vector(-34.213100,-20.087975,0)))
geoList.append(Part.LineSegment(App.Vector(-34.213100,-20.087975,0),App.Vector(-34.213100,23.998047,0)))
App.getDocument('Unnamed').getObject('Sketch').addGeometry(geoList,False)
conList = []
conList.append(Sketcher.Constraint('Coincident',0,2,1,1))
conList.append(Sketcher.Constraint('Coincident',1,2,2,1))
conList.append(Sketcher.Constraint('Coincident',2,2,3,1))
conList.append(Sketcher.Constraint('Coincident',3,2,0,1))
conList.append(Sketcher.Constraint('Horizontal',0))
conList.append(Sketcher.Constraint('Horizontal',2))
conList.append(Sketcher.Constraint('Vertical',1))
conList.append(Sketcher.Constraint('Vertical',3))
App.getDocument('Unnamed').getObject('Sketch').addConstraint(conList)
del geoList, conList

# Gui.runCommand('Sketcher_ConstrainDistanceX',0)
# Gui.Selection.addSelection('Unnamed','Body','Sketch.Edge1',12.5122,23.998,0)
App.getDocument('Unnamed').getObject('Sketch').addConstraint(Sketcher.Constraint('DistanceX',0,1,0,2,68.035194))
App.getDocument('Unnamed').getObject('Sketch').renameConstraint(8, u'lr1')
# Gui.Selection.clearSelection()
# Gui.runCommand('Sketcher_ConstrainDistanceX',0)
# Gui.runCommand('Sketcher_ConstrainDistanceY',0)
# Gui.Selection.addSelection('Unnamed','Body','Sketch.Edge2',33.8221,15.4936,0)
App.getDocument('Unnamed').getObject('Sketch').addConstraint(Sketcher.Constraint('DistanceY',1,2,1,1,44.086022))
App.getDocument('Unnamed').getObject('Sketch').setDatum(9,App.Units.Quantity('22.000000 mm'))
App.getDocument('Unnamed').getObject('Sketch').renameConstraint(9, u'wr1')
# Gui.Selection.clearSelection()
# Gui.runCommand('Std_Undo',0)
# Gui.runCommand('Std_Undo',0)
# Gui.runCommand('Std_Undo',0)
# Gui.runCommand('Std_Redo',0)
# Gui.Selection.addSelection('Unnamed','Body','Sketch.Edge2',33.8221,18.2307,0)
App.getDocument('Unnamed').getObject('Sketch').addConstraint(Sketcher.Constraint('DistanceY',1,2,1,1,44.086022))
App.getDocument('Unnamed').getObject('Sketch').setDatum(8,App.Units.Quantity('21.000000 mm'))
App.getDocument('Unnamed').getObject('Sketch').renameConstraint(8, u'lr1')
# Gui.Selection.clearSelection()
# Gui.runCommand('Std_Undo',0)
# Gui.Selection.addSelection('Unnamed','Body','Sketch.Edge2',33.8221,10.7038,0)
App.getDocument('Unnamed').getObject('Sketch').addConstraint(Sketcher.Constraint('DistanceY',1,2,1,1,44.086022))
App.getDocument('Unnamed').getObject('Sketch').setDatum(8,App.Units.Quantity('21.000000 mm'))
App.getDocument('Unnamed').getObject('Sketch').renameConstraint(8, u'wr1')
# Gui.Selection.clearSelection()
# Gui.runCommand('Sketcher_ConstrainDistanceX',0)
# Gui.Selection.addSelection('Unnamed','Body','Sketch.Edge1',7.33138,9.46802,0)
App.getDocument('Unnamed').getObject('Sketch').addConstraint(Sketcher.Constraint('DistanceX',0,1,0,2,68.035194))
App.getDocument('Unnamed').getObject('Sketch').setDatum(9,App.Units.Quantity('22.000000 mm'))
App.getDocument('Unnamed').getObject('Sketch').renameConstraint(9, u'lr1')
# Gui.Selection.clearSelection()
# Gui.runCommand('Sketcher_ConstrainSymmetric',0)
# Gui.Selection.addSelection('Unnamed','Body','Sketch.Edge4',-1.91612,3.47019,0)
# Gui.Selection.clearSelection()
# Gui.Selection.addSelection('Unnamed','Body','Sketch.Edge2',20.0839,3.37244,0)
# Gui.Selection.addSelection('Unnamed','Body','Sketch.RootPoint')
App.getDocument('Unnamed').getObject('Sketch').addConstraint(Sketcher.Constraint('Symmetric',1,1,1,2,-1,1))
# Gui.Selection.clearSelection()
# Gui.runCommand('Std_Undo',0)
# Gui.Selection.addSelection('Unnamed','Body','Sketch.Edge4',-1.91612,4.54546,0)
# Gui.Selection.clearSelection()
# Gui.Selection.addSelection('Unnamed','Body','Sketch.Edge4',-1.91612,-7.2825,0)
# Gui.runCommand('Std_Undo',0)
# Gui.runCommand('Std_Redo',0)
# Gui.runCommand('Std_Undo',0)
# Gui.runCommand('Std_Undo',0)
# Gui.runCommand('Std_Undo',0)
# Gui.runCommand('Std_Redo',0)
# Gui.runCommand('Std_Redo',0)
# Gui.runCommand('Std_Redo',0)
# Gui.Selection.clearSelection()
# Gui.runCommand('Sketcher_ConstrainSymmetric',0)
# Gui.Selection.addSelection('Unnamed','Body','Sketch.Edge4',-1.91612,4.34995,0)
# Gui.Selection.addSelection('Unnamed','Body','Sketch.RootPoint')
App.getDocument('Unnamed').getObject('Sketch').addConstraint(Sketcher.Constraint('Symmetric',3,1,3,2,-1,1))
# Gui.Selection.clearSelection()
# Gui.runCommand('Std_Undo',0)
# Gui.runCommand('Sketcher_ConstrainSymmetric',0)
# Gui.Selection.addSelection('Unnamed','Body','Sketch.Edge4',-1.91612,4.0567,0)
# Gui.Selection.clearSelection()
# Gui.Selection.addSelection('Unnamed','Body','Sketch.Edge1',6.15836,9.46802,0)
# Gui.runCommand('Std_Undo',0)
# Gui.runCommand('Std_Redo',0)
# Gui.Selection.addSelection('Unnamed','Body','Sketch.RootPoint')
App.getDocument('Unnamed').getObject('Sketch').addConstraint(Sketcher.Constraint('Symmetric',0,1,0,2,-1,1))
# Gui.Selection.clearSelection()
# Gui.runCommand('Std_Undo',0)
# Gui.runCommand('Sketcher_ConstrainSymmetric',0)
# Gui.Selection.addSelection('Unnamed','Body','Sketch.RootPoint')
# Gui.Selection.addSelection('Unnamed','Body','Sketch.Edge2',20.0839,3.82773,0)
# Gui.Selection.clearSelection()
# Gui.Selection.addSelection('Unnamed','Body','Sketch.RootPoint')
# Gui.Selection.addSelection('Unnamed','Body','Sketch.Vertex2',20.0839,9.46802,0)
# Gui.Selection.addSelection('Unnamed','Body','Sketch.Edge3',9.08388,-11.532,0)
App.getDocument('Unnamed').getObject('Sketch').addConstraint(Sketcher.Constraint('Symmetric',-1,1,0,2,2))
# Gui.Selection.clearSelection()
# Gui.runCommand('Std_Undo',0)
# Gui.Selection.addSelection('Unnamed','Body','Sketch.RootPoint')
# Gui.Selection.clearSelection()
# Gui.Selection.addSelection('Unnamed','Body','Sketch.RootPoint')
# Gui.Selection.addSelection('Unnamed','Body','Sketch.Edge4',-1.91612,4.94358,0)
# Gui.Selection.clearSelection()
# Gui.Selection.addSelection('Unnamed','Body','Sketch.Edge2',20.0839,2.19685,0)
# Gui.Selection.clearSelection()
# Gui.Selection.addSelection('Unnamed','Body','Sketch.Edge2',20.0839,3.39855,0)
# Gui.runCommand('Std_Undo',0)
# Gui.runCommand('Std_Redo',0)
# Gui.runCommand('Sketcher_ConstrainSymmetric',0)
# Gui.Selection.addSelection('Unnamed','Body','Sketch.Vertex1',-1.91612,9.46802,0)
App.getDocument('Unnamed').getObject('Sketch').addConstraint(Sketcher.Constraint('Symmetric',1,1,1,2,0,1))
# Gui.Selection.clearSelection()
# Gui.runCommand('Std_Undo',0)
# Gui.Selection.addSelection('Unnamed','Body','Sketch.Vertex1',-1.91612,9.46802,0)
# Gui.Selection.addSelection('Unnamed','Body','Sketch.Vertex2',20.0839,9.46802,0)
# Gui.Selection.addSelection('Unnamed','Body','Sketch.RootPoint')
App.getDocument('Unnamed').getObject('Sketch').addConstraint(Sketcher.Constraint('Symmetric',0,1,0,2,-1,1))
# Gui.Selection.clearSelection()
# Gui.runCommand('Std_Undo',0)
# Gui.Selection.addSelection('Unnamed','Body','Sketch.Edge4',-1.91612,9.17094,0)
# Gui.runCommand('Std_Undo',0)
# Gui.runCommand('Std_Redo',0)
# Gui.Selection.clearSelection()
# Gui.Selection.addSelection('Unnamed','Body','Sketch.Vertex2',20.0839,9.46802,0)
# Gui.Selection.addSelection('Unnamed','Body','Sketch.Vertex6',-1.91612,-11.532,0)
# Gui.Selection.addSelection('Unnamed','Body','Sketch.RootPoint')
App.getDocument('Unnamed').getObject('Sketch').addConstraint(Sketcher.Constraint('Symmetric',0,2,2,2,-1,1))
# Gui.Selection.clearSelection()
### Begin command Std_Save
# Gui.SendMsgToActiveView("Save")
App.getDocument("Unnamed").save()
### End command Std_Save
# Macro End: C:\Users\aadit\atelier_windows\freecad_models\macros\automation_t1.FCMacro +++++++++++++++++++++++++++++++++++++++++++++++++
